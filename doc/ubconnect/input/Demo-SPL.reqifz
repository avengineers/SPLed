# IBM Rational DOORS, 16 January 2026

# Specification: SPLED-SoftwareRequirements
- ReqIF.Description: Software Requirements for the Software Product Line Demonstrator "SPLED"
- ReqIF.Name: SPLED-SoftwareRequirements

## 1: Introduction

### 2: Purpose
This document specifies the Software Requirements for the SPLED system.
SPLED stands for "Software Product Line Engineering Demonstrator".
This SPL is intended to serve as a demonstrator for the usage of the methods, tools and processes.
The SPLED system is a configurable LED lighting system that supports multiple variants for different customer needs (Disco, Sleep, Spa)
- Name: Software Demonstartor "SPLED"

### 3: Scope

### 4: Definitions, Acronyms, and Abbreviations

### 5: References

### 6: Overview

## 7: General Description

### 8: Product Perspective

### 9: Product Functions

### 10: User Characteristics

### 11: General Constraints

### 12: Assumptions and Dependencies

## 13: Specific Requirements

### 14: Functional Requirements

#### 35: Power Management
- Name: Short Text

##### 37

##### 36: Power Button Input Processing
The system shall provide a debounced power button input to prevent spurious signals. A key press shall only be registered after its state is consistently detected for a configurable debounce period.

##### 38: Power State Control
The system shall toggle the power state between ON and OFF when the power button is pressed.

##### 39: Automatic Power Off
The system shall automatically turn off after a configurable period of user inactivity. The timeout period shall be configurable between 5 and 7200 seconds.
- Configuration: AUTO_OFF

##### 40: Inactivity Detection
The system shall detect user activity from the following inputs and reset the auto-off timer accordingly:
- Power button presses
- Up control key presses
- Down control key presses

#### 41: Light Control

##### 42: Light State Management
The light shall be in one of two states: ON or OFF. The light state shall follow the system's power state.

##### 43: Light Color Configuration
The light color shall be specified as an RGB value. The color shall be fixed but configurable at build time.

##### 44: Blinking Behavior
When the light is ON, it may exhibit a blinking behavior. The blinking rate shall be determined based on the main knob value.
- Configuration: BLINKING

#### 45: Brightness Control

##### 46: Brightness Value Range
The brightness of the light shall be represented by an integer value from 0 to 255.

##### 47: Manual Brightness Adjustment
The brightness of the light shall be adjustable by the user via the main control knob (percentage input).
- Configuration: BRIGHTNESS_ADJUSTMENT_MANUAL

##### 48: Automatic Brightness Adjustment
The brightness of the light shall be automatically adjusted based on a configurable period.
- Configuration: BRIGHTNESS_ADJUSTMENT_AUTOMATIC

#### 49: User Input

##### 50: Main Control Knob
The system shall provide a main control knob that allows the user to adjust a percentage value (0-100%) using Arrow Up and Arrow Down keys.

##### 51: Knob Value Persistence
The main control knob value shall be stored and retrievable through the RTE interfaces.

#### 52: RTE Interfaces

##### 53: Power State Interface
The system shall provide an RTE interface `RteGetPowerState()` to retrieve the current power state.

##### 54: Light Value Interface
The system shall provide an RTE interface `RteSetLightValue()` to set the light color.

##### 55: Brightness Value Interface
The system shall provide an RTE interface `RteSetBrightnessValue()` to set the brightness value.

##### 56: Key Press Interface
The system shall provide an RTE interface `RteIsKeyPressed()` to check the state of input keys.

##### 57: Main Knob Value Interface
The system shall provide RTE interfaces `RteGetMainKnobValue()` and `RteSetMainKnobValue()` to get and set the main control knob value.

###### 58

##### 59: Auto Off State Interface
The system shall provide an RTE interface `RteSetAutoOffState()` to communicate the auto-off state.
- Configuration: AUTO_OFF

### 15: External Interface Requirements

#### 16: User Interfaces

#### 17: Hardware Interfaces

#### 18: Software Interfaces

#### 19: Communications Interfaces

### 20: Performance Requirements

#### 60: Timing Requirements

##### 61: Task Period
The system components shall be executed periodically with a configurable task period (typically 10ms).

##### 62: Timer Resolution
Time-based functions shall operate with millisecond precision.

### 21: Design Constraints

#### 22: Standards Compliance

#### 23: Hardware Limitations

### 24: Attributes

#### 25: Availability

#### 26: Security

#### 27: Maintainability

#### 28: Transferability/Conversion

### 29: Other Requirements

#### 30: Operations

#### 31: Site Adaptation

## 32: Appendixes

### 33: Introduction

### 34: Data Elements
